FME workspace migration_veremap_layer.fmw

Parameters:
- PG_DATABASE_SOURCE = sigrando_vitis   # Base de données pdesi 
- PG_HOST_SOURCE = vm03.veremes.net   # Hôte pdesi 
- PG_PORT_SOURCE = 5432   # Port pdesi 
- PG_USER_SOURCE = postgres   # Nom d'utilisateur pdesi 
- PG_PASSWORD_SOURCE =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   # Mot de passe pdesi 

Readers:
- POSTGRES_1: POSTGRES from $(PG_DATABASE_SOURCE)

Writers:
- POSTGRES_3: POSTGRES to $(PG_DATABASE_SOURCE)

s_veremap.layer (reader POSTGRES_1)
    attributes: LAYER_ID int4, THEME_ID int4, LAYER_NAME varchar(100), GEOMETRY_ID int4, COORDSYS_ID int4, COPYRIGHT_ID int4, CONNECTION_ID int4, LAYER_DEF text, GROUP bool, LAYER_GROUP int4, QUERIABLE bool, ACTIVE bool, TOC_VISIBLE bool, ZOOM_SCALE int4, OPACITY int4, OPACITY_CURSOR bool, ID_METADATA varchar(250), MTD_TITRE varchar(200), MTD_VERSION varchar(200), MTD_RESUME text, MTD_PRODUCTEUR varchar(200), MTD_SCHEMA_SP varchar(200), MTD_OBJECTIF_PROD text, MTD_ECHELLE_MIN varchar(200), MTD_ECHELLE_MAX varchar(200), MTD_EXEMPLE varchar(200), MTD_REF_BIBLIO varchar(200), MTD_APERCU varchar(200), MTD_GENEALOGIE text, MTD_DATE_VALIDITE date,
      MTD_FREQUENCE_MAJ varchar(200), MTD_TEXTE_QUALITE text, MTD_DATE_SAISIE date, MTD_DATE_MAJ date, MTD_PROJECTION varchar(200), MTD_POS_INDIRECT varchar(200), MTD_CLASSES_LOC varchar(200), MTD_FICHIER_EXTENT varchar(200), MTD_NOM_SURFACE varchar(200), MTD_VALIDITE_EMPRISE varchar(200), MTD_DESCRIPTION varchar(200), MTD_OBJETS text, MTD_DIFFUSEUR varchar(200), MTD_ABREG_DIF varchar(200), MTD_ADR_DIF varchar(200), MTD_URL_ORG varchar(200), MTD_CONTACT varchar(200), MTD_ROLE varchar(200), MTD_ADR_CONTACT varchar(200), MTD_TEL_CONTACT varchar(200), MTD_FAX_CONTACT varchar(200), MTD_EMAIL_CONTACT varchar(200), MTD_RESTR_DIF varchar(200), MTD_PROPRIETE varchar(200), MTD_UNITE_DIF varchar(200), MTD_SUPPORT_DIF varchar(200), MTD_FORMAT_DIF varchar(200), MTD_ACCES_DIF varchar(200), MTD_SERVICES_DIF varchar(200), TABLE_FIELD_ID varchar(50),
      TABLE_SCHEMA varchar(50), TABLE_NAME varchar(50), LAYER_TITLE varchar(100), use_for_wms bool
    -> StringReplacer
StringReplacer
    FIND_TEXT = STATUS DEFAULT
    REGEXP = NO
    NO_MATCH = _FME_NO_OP_
    CASE = NO
    REPLACE_TEXT = STATUS ON
    SRC_ATTRS = LAYER_DEF
    -> StringSearcher
StringSearcher
    REGEXP = METADATA
    CASE = no
    MATCHED_RESULT_ATTR = _first_match
    STRING_TO_SEARCH = @Value(LAYER_DEF)
    MATCHED -> s_veremap.layer (writer POSTGRES_3)
    NOT_MATCHED -> StringReplacer_2
StringReplacer_2
    FIND_TEXT = [COORDSYS]
    REGEXP = NO
    NO_MATCH = _FME_NO_OP_
    CASE = NO
    REPLACE_TEXT:
      [COORDSYS]

      	METADATA
      		"wms_title" 			"[LAYER_NAME]"
      		"wms_srs" 				"EPSG:2154 EPSG:3857 EPSG:4326 EPSG:27572"
      		"wms_name" 				"[LAYER_NAME]"
      		"wms_server_version" 	"1.3.0"
      		"wms_format" 			"image/png"
      	END
    SRC_ATTRS = LAYER_DEF
    -> s_veremap.layer (writer POSTGRES_3)
s_veremap.layer (writer POSTGRES_3)
    attributes: LAYER_ID int4, THEME_ID int4, LAYER_NAME varchar(100), GEOMETRY_ID int4, COORDSYS_ID int4, COPYRIGHT_ID int4, CONNECTION_ID int4, LAYER_DEF text, GROUP bool, LAYER_GROUP int4, QUERIABLE bool, ACTIVE bool, TOC_VISIBLE bool, ZOOM_SCALE int4, OPACITY int4, OPACITY_CURSOR bool, ID_METADATA varchar(250), MTD_TITRE varchar(200), MTD_VERSION varchar(200), MTD_RESUME text, MTD_PRODUCTEUR varchar(200), MTD_SCHEMA_SP varchar(200), MTD_OBJECTIF_PROD text, MTD_ECHELLE_MIN varchar(200), MTD_ECHELLE_MAX varchar(200), MTD_EXEMPLE varchar(200), MTD_REF_BIBLIO varchar(200), MTD_APERCU varchar(200), MTD_GENEALOGIE text, MTD_DATE_VALIDITE date,
      MTD_FREQUENCE_MAJ varchar(200), MTD_TEXTE_QUALITE text, MTD_DATE_SAISIE date, MTD_DATE_MAJ date, MTD_PROJECTION varchar(200), MTD_POS_INDIRECT varchar(200), MTD_CLASSES_LOC varchar(200), MTD_FICHIER_EXTENT varchar(200), MTD_NOM_SURFACE varchar(200), MTD_VALIDITE_EMPRISE varchar(200), MTD_DESCRIPTION varchar(200), MTD_OBJETS text, MTD_DIFFUSEUR varchar(200), MTD_ABREG_DIF varchar(200), MTD_ADR_DIF varchar(200), MTD_URL_ORG varchar(200), MTD_CONTACT varchar(200), MTD_ROLE varchar(200), MTD_ADR_CONTACT varchar(200), MTD_TEL_CONTACT varchar(200), MTD_FAX_CONTACT varchar(200), MTD_EMAIL_CONTACT varchar(200), MTD_RESTR_DIF varchar(200), MTD_PROPRIETE varchar(200), MTD_UNITE_DIF varchar(200), MTD_SUPPORT_DIF varchar(200), MTD_FORMAT_DIF varchar(200), MTD_ACCES_DIF varchar(200), MTD_SERVICES_DIF varchar(200), TABLE_FIELD_ID varchar(50),
      TABLE_SCHEMA varchar(50), TABLE_NAME varchar(50), LAYER_TITLE varchar(100), use_for_wms bool
