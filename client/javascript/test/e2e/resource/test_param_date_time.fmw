FME workspace test_param_date_time.fmw
Title: Param date time
Description: Projet pour tester le paramètre publié de type Date Time
Usage: Test de GTF Vitis angular
Requirements: RAS

Parameters:
- date_time = 20160325110700   # Sélectionner les depts dont la date de création est postérieure au
- H_DestDataset_MITAB = E:\margot\gtf\2015\recette\date_time   # Destination MapInfo Folder

Readers:
- SHAPE_1: SHAPE from $(FME_MF_DIR)depts.zip

Writers:
- MITAB_1: MITAB to $(H_DestDataset_MITAB)

depts (reader SHAPE_1)
    attributes: NUM_DEP char(2), NB_COMM number(5,0), NOM_DEP char(30), POP_DEP number(16,0), SURF_KM2 number(16,2), NUM_REG number(3,0), NOM_REG char(50), date char(200)
    -> DateFormatter
DateFormatter
    FMT = FME Date/Time (%Y%m%d%H%M%S)
    SRCFMT = Unknown - Automatic Detection
    INVALID_DATE_VALUE = _FME_NO_OP_
    DATE_ATTR = date
    -> Tester
Tester
    BOOL_OP = OR
    TEST_CLAUSE = TEST @Value(date) > $(date_time)
    TEST_MODE = Automatic
    TEST_DESCRIPTION = ""
    PASSED -> dept (writer MITAB_1)
dept (writer MITAB_1)
    attributes: NUM_DEP char(2), NB_COMM float, NOM_DEP char(30), POP_DEP float, SURF_KM2 float, NUM_REG float, NOM_REG char(50), date char(200)
