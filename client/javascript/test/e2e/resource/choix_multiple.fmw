FME workspace choix_multiple.fmw

Parameters:
- dept =
- fest =
- DestDataset_SHAPE = it3   # Dossier destination 

Readers:
- SHAPE_1: SHAPE from $(FME_MF_DIR_UNIX)/DPT.SHP

Writers:
- SHAPE_2: SHAPE to $(DestDataset_SHAPE)

DPT (reader SHAPE_1)
    attributes: NUM_DEP char(2), NB_COMM number(5,0), NOM_DEP char(30), POP_DEP number(16,0), SURF_KM2 number(16,2), NUM_REG number(3,0), NOM_REG char(50)
    -> Tester
Tester
    TEST_CLAUSE = TEST @Value(NOM_DEP) = $(dept)
    TEST_MODE = Automatic
    TEST_DESCRIPTION = ""
    BOOL_OP = OR
    PASSED -> AttributeCreator
AttributeCreator
    ATTR_LIST = festivals,$(fest)
    -> DPT (writer SHAPE_2)
DPT (writer SHAPE_2)
    attributes: NUM_DEP char(2), NB_COMM number(5,0), NOM_DEP char(30), POP_DEP number(16,0), SURF_KM2 number(16,2), NUM_REG number(3,0), NOM_REG char(50), festivals char(50)
