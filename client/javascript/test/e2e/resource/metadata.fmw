FME workspace metadata.fmw
Title: métadonnées
Description: Projet pour tester l'import de métadonnées dans GTF
éàçù! 
Description
Usage: Projet pour tester l'import de métadonnées dans GTF
éàçù! 
Utilisation
Requirements: Projet pour tester l'import de métadonnées dans GTF
éàçù! 
Pré requis
Legal terms conditions: Projet pour tester l'import de métadonnées dans GTF
éàçù! 
Conditions d'utilisation

Parameters:
- Source_ = E:\data\shp\dpt\DPT.SHP   # Fichier source shape 
- DestDataset_MAPINFO = E:\margot\gtf\2016\metadata   # Dossier destination MapInfo 

Readers:
- SHAPE_1: SHAPE from $(Source_)

Writers:
- MAPINFO_1: MAPINFO to $(DestDataset_MAPINFO)

dpt2 (reader SHAPE_1)
    attributes: NUM_DEP char(2), NB_COMM number(5,0), NOM_DEP char(30), POP_DEP number(16,0), SURF_KM2 number(16,2), NUM_REG number(3,0), NOM_REG char(50)
    -> Table2 (writer MAPINFO_1)
Table2 (writer MAPINFO_1)
